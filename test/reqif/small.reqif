# ReqIF export for Project 10201 from OSLC adapter for Jira

## R1: Spotting fire (Requirement)
The system shall alert the control center if it spots a fire in a forest.
- Decomposed By -> R4
- Decomposes -> R3

## R2: First API requirement (Requirement)
Test description
- Decomposed By -> R4
- Decomposes -> R3

## R3: Observe earths surface. (Requirement)
The system shall observe the earths surface.
- Decomposed By -> R1
- Decomposed By -> R2
- Decomposes -> R4

## R4: Fast system (Requirement Collection)
- Decomposed By -> R3
- Decomposes -> R1
- Decomposes -> R2
